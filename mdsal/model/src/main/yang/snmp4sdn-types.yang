module snmp4sdn-types {
    yang-version 1;

    namespace "urn:opendaylight:snmp4sdn:md:types";
    prefix snmp4sdn-types;

    organization "Industrial Technology Research Institute of Taiwan";
    contact "Yi-Ling Hsieh <ylhsieh@itri.org.tw>";

    description "YANG version of the SNMP4SDN FDB Service MIB.";

    revision "2015-01-26" {//TODO: update date
        description
            "SNMP4SDN common MD types";
    }

    typedef result{
        type enumeration{
            enum "SUCCESS" {
                value 1;
            }
            enum "FAIL" {
                value 2;
            }
            enum "EMPTY" {
                value 3;
            }
            enum "INVALID_PARAM" {
                value 4;
            }
            enum "ALREADY_EXIST" {
                value 5;
            }
            enum "NOT_EXIST" {
                value 6;
            }
            enum "NOT_READY" {
                value 7;
            }
            enum "INTERRUPT" {
                value 8;
             }
        }
    }
}
