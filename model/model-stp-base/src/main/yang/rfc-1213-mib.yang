/*
 * This YANG module has been generated by smidump 0.4.8:
 *
 *      smidump -f yang RFC1213-MIB
 *
 * Do not edit. Edit the source file instead!
 */

/*
 * WARNING: this output may be incorrect due to significant parse errors
 */

module RFC1213-MIB {

  namespace "urn:ietf:params:xml:ns:yang:smiv2:RFC1213-MIB";
  prefix "rfc1213-mib";

  import ietf-yang-types {prefix "yang";}

  revision "2013-10-17" {
        description "Initial revision of RFC1213-MIB model";
  }
}
