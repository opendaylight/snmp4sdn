/*
 * This YANG module has been generated by smidump 0.4.8:
 *
 *      smidump -f yang SNMPv2-TC
 *
 * Do not edit. Edit the source file instead!
 */

/*
 * WARNING: this output may be incorrect due to significant parse errors
 */

module SNMPv2-TC {

  namespace "urn:ietf:params:xml:ns:yang:smiv2:SNMPv2-TC";
  prefix "snmpv2-tc";

  import ietf-yang-types {
    prefix "yang";
  }

  revision "2013-10-17" {
        description "Initial revision of SNMPv2-TC model";
  }

  typedef DisplayString {
    type string {
      length "0..255";
    }
    description
     "Represents textual information taken from the NVT ASCII
      
      
      RFC 2579             Textual Conventions for SMIv2            April 1999
      
      
      character set, as defined in pages 4, 10-11 of RFC 854.
      
      To summarize RFC 854, the NVT ASCII repertoire specifies:
      
        - the use of character codes 0-127 (decimal)
      
        - the graphics characters (32-126) are interpreted as
          US ASCII
      
        - NUL, LF, CR, BEL, BS, HT, VT and FF have the special
          meanings specified in RFC 854
      
        - the other 25 codes have no standard interpretation
      
        - the sequence 'CR LF' means newline
      
        - the sequence 'CR NUL' means carriage-return
      
        - an 'LF' not preceded by a 'CR' means moving to the
          same column on the next line.
      
        - the sequence 'CR x' for any x other than LF or NUL is
          illegal.  (Note that this also means that a string may
          end with either 'CR LF' or 'CR NUL', but not with CR.)
      
      Any object defined using this syntax may not exceed 255
      characters in length.";
  }

  typedef PhysAddress {
    type string;
    description
     "Represents media- or physical-level addresses.";
  }

  typedef MacAddress {
    type string {
      length "6";
    }
    description
     "Represents an 802 MAC address represented in the
      `canonical' order defined by IEEE 802.1a, i.e., as if it
      were transmitted least significant bit first, even though
      802.5 (in contrast to other 802.x protocols) requires MAC
      addresses to be transmitted most significant bit first.";
  }

  typedef TestAndIncr {
    type int32 {
      range "0..2147483647";
    }
    description
     "Represents integer-valued information used for atomic
      operations.  When the management protocol is used to specify
      that an object instance having this syntax is to be
      modified, the new value supplied via the management protocol
      must precisely match the value presently held by the
      instance.  If not, the management protocol set operation
      fails with an error of `inconsistentValue'.  Otherwise, if
      the current value is the maximum value of 2^31-1 (2147483647
      decimal), then the value held by the instance is wrapped to
      zero; otherwise, the value held by the instance is
      incremented by one.  (Note that regardless of whether the
      management protocol set operation succeeds, the variable-
      binding in the request and response PDUs are identical.)
      
      The value of the ACCESS clause for objects having this
      syntax is either `read-write' or `read-create'.  When an
      instance of a columnar object having this syntax is created,
      any value may be supplied via the management protocol.
      
      When the network management portion of the system is re-
      initialized, the value of every object instance having this
      syntax must either be incremented from its value prior to
      the re-initialization, or (if the value prior to the re-
      initialization is unknown) be set to a pseudo-randomly
      generated value.";
  }

  typedef AutonomousType {
    type yang:object-identifier;
    description
     "Represents an independently extensible type identification
      value.  It may, for example, indicate a particular sub-tree
      with further MIB definitions, or define a particular type of
      protocol or hardware.";
  }

  typedef TimeStamp {
    type yang:timeticks;
    description
     "The value of the sysUpTime object at which a specific
      occurrence happened.  The specific occurrence must be
      
      
      RFC 2579             Textual Conventions for SMIv2            April 1999
      
      
      defined in the description of any object defined using this
      type.
      
      If sysUpTime is reset to zero as a result of a re-
      initialization of the network management (sub)system, then
      the values of all TimeStamp objects are also reset.
      However, after approximately 497 days without a re-
      initialization, the sysUpTime object will reach 2^^32-1 and
      then increment around to zero; in this case, existing values
      of TimeStamp objects do not change.  This can lead to
      ambiguities in the value of TimeStamp objects.";
  }

  typedef TimeInterval {
    type int32 {
      range "0..2147483647";
    }
    description
     "A period of time, measured in units of 0.01 seconds.";
  }

  typedef DateAndTime {
    type string {
      length "8|11";
    }
    description
     "A date-time specification.
      
      field  octets  contents                  range
      -----  ------  --------                  -----
        1      1-2   year*                     0..65536
        2       3    month                     1..12
        3       4    day                       1..31
        4       5    hour                      0..23
        5       6    minutes                   0..59
        6       7    seconds                   0..60
                     (use 60 for leap-second)
        7       8    deci-seconds              0..9
        8       9    direction from UTC        '+' / '-'
        9      10    hours from UTC*           0..13
       10      11    minutes from UTC          0..59
      
      * Notes:
      - the value of year is in network-byte order
      - daylight saving time in New Zealand is +13
      
      For example, Tuesday May 26, 1992 at 1:30:15 PM EDT would be
      displayed as:
      
                       1992-5-26,13:30:15.0,-4:0
      
      
      RFC 2579             Textual Conventions for SMIv2            April 1999
      
      
      Note that if only local time is known, then timezone
      information (fields 8-10) is not present.";
  }

  typedef StorageType {
    type enumeration {
      enum "other" {
        value "1";
      }
      enum "volatile" {
        value "2";
      }
      enum "nonVolatile" {
        value "3";
      }
      enum "permanent" {
        value "4";
      }
      enum "readOnly" {
        value "5";
      }
    }
    description
     "Describes the memory realization of a conceptual row.  A
      row which is volatile(2) is lost upon reboot.  A row which
      is either nonVolatile(3), permanent(4) or readOnly(5), is
      backed up by stable storage.  A row which is permanent(4)
      can be changed but not deleted.  A row which is readOnly(5)
      cannot be changed nor deleted.
      
      If the value of an object with this syntax is either
      permanent(4) or readOnly(5), it cannot be written.
      Conversely, if the value is either other(1), volatile(2) or
      nonVolatile(3), it cannot be modified to be permanent(4) or
      readOnly(5).  (All illegal modifications result in a
      'wrongValue' error.)
      
      Every usage of this textual convention is required to
      specify the columnar objects which a permanent(4) row must
      at a minimum allow to be writable.";
  }

  
  typedef TruthValue {
    type enumeration {
      enum "true" {
        value "1";
      }
      enum "false" {
        value "2";
      }
    }
  }
}
