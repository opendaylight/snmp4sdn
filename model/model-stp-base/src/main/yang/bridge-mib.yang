/*
 * This YANG module has been generated by smidump 0.4.8:
 *
 *      smidump -f yang BRIDGE-MIB
 *
 * Do not edit. Edit the source file instead!
 */

/*
 * WARNING: this output may be incorrect due to significant parse errors
 */

module BRIDGE-MIB {

  namespace "urn:ietf:params:xml:ns:yang:smiv2:BRIDGE-MIB";
  prefix "bridge-mib";

//  import RFC-1212 {
//    prefix "rfc-1212";
//  }

//  import RFC-1215 {
//    prefix "rfc-1215";
//  }

  import RFC1213-MIB {
    prefix "rfc1213-mib";
  }

  import ietf-yang-types {
    prefix "yang";
  }

  revision "2013-10-17" {
        description "Initial revision of BRIDGE-MIB model";
  }
  
  typedef MacAddress {
    type binary {
      length "6";
    }
  }

  typedef BridgeId {
    type binary {
      length "8";
    }
  }

  typedef Timeout {
    type int32;
  }


  leaf dot1dBaseBridgeAddress {
    type bridge-mib:MacAddress;
    description
     "The MAC address used by this bridge when it must
      be referred to in a unique fashion.   It is
      recommended that this be the numerically smallest
      MAC address of all ports that belong to this
      bridge.  However it is only required to be unique.
      When concatenated with dot1dStpPriority a unique
      BridgeIdentifier is formed which is used in the
      Spanning Tree Protocol.";
    reference
     "IEEE 802.1D-1990: Sections 6.4.1.1.3 and 3.12.5";
  }


  leaf dot1dBaseNumPorts {
    type int32;
    description
     "The number of ports controlled by this bridging
      entity.";
    reference
     "IEEE 802.1D-1990: Section 6.4.1.1.3";
  }


  leaf dot1dBaseType {
    type enumeration {
      enum "unknown" {
        value "1";
      }
      enum "transparent-only" {
        value "2";
      }
      enum "sourceroute-only" {
        value "3";
      }
      enum "srt" {
        value "4";
      }
    }
    description
     "Indicates what type of bridging this bridge can
      perform.  If a bridge is actually performing a
      certain type of bridging this will be indicated by
      entries in the port table for the given type.";
  }


  leaf dot1dStpProtocolSpecification {
    type enumeration {
      enum "unknown" {
        value "1";
      }
      enum "decLb100" {
        value "2";
      }
      enum "ieee8021d" {
        value "3";
      }
    }
    description
     "An indication of what version of the Spanning
      Tree Protocol is being run.  The value
      'decLb100(2)' indicates the DEC LANbridge 100
      Spanning Tree protocol.  IEEE 802.1d
      implementations will return 'ieee8021d(3)'.  If
      future versions of the IEEE Spanning Tree Protocol
      are released that are incompatible with the
      current version a new value will be defined.";
  }


  leaf dot1dStpPriority {
    type int32 {
      range "0..65535";
    }
    description
     "The value of the write-able portion of the Bridge
      ID, i.e., the first two octets of the (8 octet
      long) Bridge ID.  The other (last) 6 octets of the
      Bridge ID are given by the value of
      dot1dBaseBridgeAddress.";
    reference
     "IEEE 802.1D-1990: Section 4.5.3.7";
  }


  leaf dot1dStpTimeSinceTopologyChange {
    type yang:timeticks;
    description
     "The time (in hundredths of a second) since the
      last time a topology change was detected by the
      bridge entity.";
    reference
     "IEEE 802.1D-1990: Section 6.8.1.1.3";
  }


  leaf dot1dStpTopChanges {
    type yang:counter32;
    description
     "The total number of topology changes detected by
      this bridge since the management entity was last
      reset or initialized.";
    reference
     "IEEE 802.1D-1990: Section 6.8.1.1.3";
  }


  leaf dot1dStpDesignatedRoot {
    type bridge-mib:BridgeId;
    description
     "The bridge identifier of the root of the spanning
      tree as determined by the Spanning Tree Protocol
      as executed by this node.  This value is used as
      
      
      
      the Root Identifier parameter in all Configuration
      Bridge PDUs originated by this node.";
    reference
     "IEEE 802.1D-1990: Section 4.5.3.1";
  }


  leaf dot1dStpRootCost {
    type int32;
    description
     "The cost of the path to the root as seen from
      this bridge.";
    reference
     "IEEE 802.1D-1990: Section 4.5.3.2";
  }


  leaf dot1dStpRootPort {
    type int32;
    description
     "The port number of the port which offers the
      lowest cost path from this bridge to the root
      bridge.";
    reference
     "IEEE 802.1D-1990: Section 4.5.3.3";
  }


  leaf dot1dStpMaxAge {
    type bridge-mib:Timeout;
    description
     "The maximum age of Spanning Tree Protocol
      information learned from the network on any port
      before it is discarded, in units of hundredths of
      a second.  This is the actual value that this
      bridge is currently using.";
    reference
     "IEEE 802.1D-1990: Section 4.5.3.4";
  }


  leaf dot1dStpHelloTime {
    type bridge-mib:Timeout;
    description
     "The amount of time between the transmission of
      Configuration bridge PDUs by this node on any port
      when it is the root of the spanning tree or trying
      to become so, in units of hundredths of a second.
      This is the actual value that this bridge is
      currently using.";
    reference
     "IEEE 802.1D-1990: Section 4.5.3.5";
  }


  leaf dot1dStpHoldTime {
    type int32;
    description
     "This time value determines the interval length
      during which no more than two Configuration bridge
      PDUs shall be transmitted by this node, in units
      of hundredths of a second.";
    reference
     "IEEE 802.1D-1990: Section 4.5.3.14";
  }


  leaf dot1dStpForwardDelay {
    type bridge-mib:Timeout;
    description
     "This time value, measured in units of hundredths
      of a second, controls how fast a port changes its
      spanning state when moving towards the Forwarding
      state.  The value determines how long the port
      stays in each of the Listening and Learning
      states, which precede the Forwarding state.  This
      value is also used, when a topology change has
      been detected and is underway, to age all dynamic
      entries in the Forwarding Database.  [Note that
      this value is the one that this bridge is
      currently using, in contrast to
      dot1dStpBridgeForwardDelay which is the value that
      this bridge and all others would start using
      if/when this bridge were to become the root.]";
    reference
     "IEEE 802.1D-1990: Section 4.5.3.6";
  }


  leaf dot1dStpBridgeMaxAge {
    type bridge-mib:Timeout {
      range "600..4000";
    }
    description
     "The value that all bridges use for MaxAge when
      this bridge is acting as the root.  Note that
      802.1D-1990 specifies that the range for this
      parameter is related to the value of
      dot1dStpBridgeHelloTime. The granularity of this
      timer is specified by 802.1D-1990 to be 1 second.
      An agent may return a badValue error if a set is
      attempted to a value which is not a whole number
      of seconds.";
    reference
     "IEEE 802.1D-1990: Section 4.5.3.8";
  }


  leaf dot1dStpBridgeHelloTime {
    type bridge-mib:Timeout {
      range "100..1000";
    }
    description
     "The value that all bridges use for HelloTime when
      this bridge is acting as the root.  The
      granularity of this timer is specified by 802.1D-
      1990 to be 1 second.  An agent may return a
      badValue error if a set is attempted to a value
      which is not a whole number of seconds.";
    reference
     "IEEE 802.1D-1990: Section 4.5.3.9";
  }


  leaf dot1dStpBridgeForwardDelay {
    type bridge-mib:Timeout {
      range "400..3000";
    }
    description
     "The value that all bridges use for ForwardDelay
      when this bridge is acting as the root.  Note that
      802.1D-1990 specifies that the range for this
      parameter is related to the value of
      dot1dStpBridgeMaxAge.  The granularity of this
      timer is specified by 802.1D-1990 to be 1 second.
      An agent may return a badValue error if a set is
      attempted to a value which is not a whole number
      of seconds.";
    reference
     "IEEE 802.1D-1990: Section 4.5.3.10";
  }


  leaf dot1dTpLearnedEntryDiscards {
    type yang:counter32;
    description
     "The total number of Forwarding Database entries,
      which have been or would have been learnt, but
      have been discarded due to a lack of space to
      store them in the Forwarding Database.  If this
      counter is increasing, it indicates that the
      Forwarding Database is regularly becoming full (a
      condition which has unpleasant performance effects
      on the subnetwork).  If this counter has a
      significant value but is not presently increasing,
      it indicates that the problem has been occurring
      but is not persistent.";
    reference
     "IEEE 802.1D-1990: Section 6.7.1.1.3";
  }


  leaf dot1dTpAgingTime {
    type int32 {
      range "10..1000000";
    }
    description
     "The timeout period in seconds for aging out
      dynamically learned forwarding information.
      802.1D-1990 recommends a default of 300 seconds.";
    reference
     "IEEE 802.1D-1990: Section 6.7.1.1.3";
  }


  container dot1dBasePortTable {
    config false;
    description
     "A table that contains generic information about
      every port that is associated with this bridge.
      Transparent, source-route, and srt ports are
      included.";

    list dot1dBasePortEntry {
      key "dot1dBasePort";
      description
       "A list of information for each port of the
        bridge.";
      reference
       "IEEE 802.1D-1990: Section 6.4.2, 6.6.1";

      leaf dot1dBasePort {
        type int32 {
          range "1..65535";
        }
        description
         "The port number of the port for which this entry
          contains bridge management information.";
      }

      leaf dot1dBasePortIfIndex {
        type int32;
        description
         "The value of the instance of the ifIndex object,
          defined in MIB-II, for the interface corresponding
          to this port.";
      }

      leaf dot1dBasePortCircuit {
        type yang:object-identifier;
        description
         "For a port which (potentially) has the same value
          of dot1dBasePortIfIndex as another port on the
          same bridge, this object contains the name of an
          object instance unique to this port.  For example,
          in the case where multiple ports correspond one-
          to-one with multiple X.25 virtual circuits, this
          value might identify an (e.g., the first) object
          instance associated with the X.25 virtual circuit
          corresponding to this port.
          
          For a port which has a unique value of
          dot1dBasePortIfIndex, this object can have the
          value { 0 0 }.";
      }

      leaf dot1dBasePortDelayExceededDiscards {
        type yang:counter32;
        description
         "The number of frames discarded by this port due
          to excessive transit delay through the bridge.  It
          is incremented by both transparent and source
          route bridges.";
        reference
         "IEEE 802.1D-1990: Section 6.6.1.1.3";
      }

      leaf dot1dBasePortMtuExceededDiscards {
        type yang:counter32;
        description
         "The number of frames discarded by this port due
          to an excessive size.  It is incremented by both
          transparent and source route bridges.";
        reference
         "IEEE 802.1D-1990: Section 6.6.1.1.3";
      }
    }
  }


  container dot1dStpPortTable {
    config false;
    description
     "A table that contains port-specific information
      for the Spanning Tree Protocol.";

    list dot1dStpPortEntry {
      key "dot1dStpPort";
      description
       "A list of information maintained by every port
        about the Spanning Tree Protocol state for that
        port.";

      leaf dot1dStpPort {
        type int32 {
          range "1..65535";
        }
        description
         "The port number of the port for which this entry
          contains Spanning Tree Protocol management
          information.";
        reference
         "IEEE 802.1D-1990: Section 6.8.2.1.2";
      }

      leaf dot1dStpPortPriority {
        type int32 {
          range "0..255";
        }
        description
         "The value of the priority field which is
          contained in the first (in network byte order)
          octet of the (2 octet long) Port ID.  The other
          octet of the Port ID is given by the value of
          dot1dStpPort.";
        reference
         "IEEE 802.1D-1990: Section 4.5.5.1";
      }

      leaf dot1dStpPortState {
        type enumeration {
          enum "disabled" {
            value "1";
          }
          enum "blocking" {
            value "2";
          }
          enum "listening" {
            value "3";
          }
          enum "learning" {
            value "4";
          }
          enum "forwarding" {
            value "5";
          }
          enum "broken" {
            value "6";
          }
        }
        description
         "The port's current state as defined by
          application of the Spanning Tree Protocol.  This
          state controls what action a port takes on
          reception of a frame.  If the bridge has detected
          a port that is malfunctioning it will place that
          port into the broken(6) state.  For ports which
          are disabled (see dot1dStpPortEnable), this object
          will have a value of disabled(1).";
        reference
         "IEEE 802.1D-1990: Section 4.5.5.2";
      }

      leaf dot1dStpPortEnable {
        type enumeration {
          enum "enabled" {
            value "1";
          }
          enum "disabled" {
            value "2";
          }
        }
        description
         "The enabled/disabled status of the port.";
        reference
         "IEEE 802.1D-1990: Section 4.5.5.2";
      }

      leaf dot1dStpPortPathCost {
        type int32 {
          range "1..65535";
        }
        description
         "The contribution of this port to the path cost of
          paths towards the spanning tree root which include
          this port.  802.1D-1990 recommends that the
          default value of this parameter be in inverse
          proportion to the speed of the attached LAN.";
        reference
         "IEEE 802.1D-1990: Section 4.5.5.3";
      }

      leaf dot1dStpPortDesignatedRoot {
        type bridge-mib:BridgeId;
        description
         "The unique Bridge Identifier of the Bridge
          recorded as the Root in the Configuration BPDUs
          transmitted by the Designated Bridge for the
          segment to which the port is attached.";
        reference
         "IEEE 802.1D-1990: Section 4.5.5.4";
      }

      leaf dot1dStpPortDesignatedCost {
        type int32;
        description
         "The path cost of the Designated Port of the
          segment connected to this port.  This value is
          compared to the Root Path Cost field in received
          
          
          
          bridge PDUs.";
        reference
         "IEEE 802.1D-1990: Section 4.5.5.5";
      }

      leaf dot1dStpPortDesignatedBridge {
        type bridge-mib:BridgeId;
        description
         "The Bridge Identifier of the bridge which this
          port considers to be the Designated Bridge for
          this port's segment.";
        reference
         "IEEE 802.1D-1990: Section 4.5.5.6";
      }

      leaf dot1dStpPortDesignatedPort {
        type binary {
          length "2";
        }
        description
         "The Port Identifier of the port on the Designated
          Bridge for this port's segment.";
        reference
         "IEEE 802.1D-1990: Section 4.5.5.7";
      }

      leaf dot1dStpPortForwardTransitions {
        type yang:counter32;
        description
         "The number of times this port has transitioned
          from the Learning state to the Forwarding state.";
      }
    }
  }


  container dot1dTpFdbTable {
    config false;
    description
     "A table that contains information about unicast
      entries for which the bridge has forwarding and/or
      filtering information.  This information is used
      by the transparent bridging function in
      determining how to propagate a received frame.";

    list dot1dTpFdbEntry {
      key "dot1dTpFdbAddress";
      description
       "Information about a specific unicast MAC address
        for which the bridge has some forwarding and/or
        filtering information.";

      leaf dot1dTpFdbAddress {
        type bridge-mib:MacAddress;
        description
         "A unicast MAC address for which the bridge has
          forwarding and/or filtering information.";
        reference
         "IEEE 802.1D-1990: Section 3.9.1, 3.9.2";
      }

      leaf dot1dTpFdbPort {
        type int32;
        description
         "Either the value '0', or the port number of the
          port on which a frame having a source address
          equal to the value of the corresponding instance
          of dot1dTpFdbAddress has been seen.  A value of
          '0' indicates that the port number has not been
          learned but that the bridge does have some
          forwarding/filtering information about this
          address (e.g. in the dot1dStaticTable).
          Implementors are encouraged to assign the port
          value to this object whenever it is learned even
          for addresses for which the corresponding value of
          dot1dTpFdbStatus is not learned(3).";
      }

      leaf dot1dTpFdbStatus {
        type enumeration {
          enum "other" {
            value "1";
          }
          enum "invalid" {
            value "2";
          }
          enum "learned" {
            value "3";
          }
          enum "self" {
            value "4";
          }
          enum "mgmt" {
            value "5";
          }
        }
        description
         "The status of this entry.  The meanings of the
          values are:
          
            other(1)   : none of the following.  This would
                         include the case where some other
                         MIB object (not the corresponding
                         instance of dot1dTpFdbPort, nor an
                         entry in the dot1dStaticTable) is
                         being used to determine if and how
                         frames addressed to the value of
                         the corresponding instance of
                         dot1dTpFdbAddress are being
                         forwarded.
          
            invalid(2) : this entry is not longer valid
                         (e.g., it was learned but has since
                         aged-out), but has not yet been
                         flushed from the table.
          
            learned(3) : the value of the corresponding
                         instance of dot1dTpFdbPort was
                         learned, and is being used.
          
            self(4)    : the value of the corresponding
                         instance of dot1dTpFdbAddress
                         represents one of the bridge's
                         addresses.  The corresponding
                         instance of dot1dTpFdbPort
                         indicates which of the bridge's
                         ports has this address.
          
            mgmt(5)    : the value of the corresponding
                         instance of dot1dTpFdbAddress is
                         also the value of an existing
                         instance of dot1dStaticAddress.";
      }
    }
  }


  container dot1dTpPortTable {
    config false;
    description
     "A table that contains information about every
      port that is associated with this transparent
      bridge.";

    list dot1dTpPortEntry {
      key "dot1dTpPort";
      description
       "A list of information for each port of a
        transparent bridge.";

      leaf dot1dTpPort {
        type int32 {
          range "1..65535";
        }
        description
         "The port number of the port for which this entry
          contains Transparent bridging management
          information.";
      }

      leaf dot1dTpPortMaxInfo {
        type int32;
        description
         "The maximum size of the INFO (non-MAC) field that
          this port will receive or transmit.";
      }

      leaf dot1dTpPortInFrames {
        type yang:counter32;
        description
         "The number of frames that have been received by
          this port from its segment. Note that a frame
          received on the interface corresponding to this
          port is only counted by this object if and only if
          it is for a protocol being processed by the local
          bridging function, including bridge management
          frames.";
        reference
         "IEEE 802.1D-1990: Section 6.6.1.1.3";
      }

      leaf dot1dTpPortOutFrames {
        type yang:counter32;
        description
         "The number of frames that have been transmitted
          by this port to its segment.  Note that a frame
          transmitted on the interface corresponding to this
          port is only counted by this object if and only if
          it is for a protocol being processed by the local
          bridging function, including bridge management
          frames.";
        reference
         "IEEE 802.1D-1990: Section 6.6.1.1.3";
      }

      leaf dot1dTpPortInDiscards {
        type yang:counter32;
        description
         "Count of valid frames received which were
          discarded (i.e., filtered) by the Forwarding
          Process.";
        reference
         "IEEE 802.1D-1990: Section 6.6.1.1.3";
      }
    }
  }


  container dot1dStaticTable {
    config false;
    description
     "A table containing filtering information
      configured into the bridge by (local or network)
      management specifying the set of ports to which
      frames received from specific ports and containing
      specific destination addresses are allowed to be
      forwarded.  The value of zero in this table as the
      port number from which frames with a specific
      destination address are received, is used to
      specify all ports for which there is no specific
      entry in this table for that particular
      destination address.  Entries are valid for
      unicast and for group/broadcast addresses.";
    reference
     "IEEE 802.1D-1990: Section 6.7.2";

    list dot1dStaticEntry {
      key "dot1dStaticAddress dot1dStaticReceivePort";
      description
       "Filtering information configured into the bridge
        by (local or network) management specifying the
        set of ports to which frames received from a
        specific port and containing a specific
        destination address are allowed to be forwarded.";
      reference
       "IEEE 802.1D-1990: Section 6.7.2";

      leaf dot1dStaticAddress {
        type bridge-mib:MacAddress;
        description
         "The destination MAC address in a frame to which
          this entry's filtering information applies.  This
          object can take the value of a unicast address, a
          group address or the broadcast address.";
        reference
         "IEEE 802.1D-1990: Section 3.9.1, 3.9.2";
      }

      leaf dot1dStaticReceivePort {
        type int32;
        description
         "Either the value '0', or the port number of the
          port from which a frame must be received in order
          for this entry's filtering information to apply.
          A value of zero indicates that this entry applies
          on all ports of the bridge for which there is no
          other applicable entry.";
      }

      leaf dot1dStaticAllowedToGoTo {
        type binary;
        description
         "The set of ports to which frames received from a
          specific port and destined for a specific MAC
          
          
          
          address, are allowed to be forwarded.  Each octet
          within the value of this object specifies a set of
          eight ports, with the first octet specifying ports
          1 through 8, the second octet specifying ports 9
          through 16, etc.  Within each octet, the most
          significant bit represents the lowest numbered
          port, and the least significant bit represents the
          highest numbered port.  Thus, each port of the
          bridge is represented by a single bit within the
          value of this object.  If that bit has a value of
          '1' then that port is included in the set of
          ports; the port is not included if its bit has a
          value of '0'.  (Note that the setting of the bit
          corresponding to the port from which a frame is
          received is irrelevant.)  The default value of
          this object is a string of ones of appropriate
          length.";
      }

      leaf dot1dStaticStatus {
        type enumeration {
          enum "other" {
            value "1";
          }
          enum "invalid" {
            value "2";
          }
          enum "permanent" {
            value "3";
          }
          enum "deleteOnReset" {
            value "4";
          }
          enum "deleteOnTimeout" {
            value "5";
          }
        }
        description
         "This object indicates the status of this entry.
          The default value is permanent(3).
          
               other(1) - this entry is currently in use but
                    the conditions under which it will
                    remain so are different from each of the
                    following values.
               invalid(2) - writing this value to the object
                    removes the corresponding entry.
               permanent(3) - this entry is currently in use
                    and will remain so after the next reset
                    of the bridge.
               deleteOnReset(4) - this entry is currently in
                    use and will remain so until the next
                    reset of the bridge.
               deleteOnTimeout(5) - this entry is currently
                    in use and will remain so until it is
                    aged out.";
      }
    }
  }

  notification newRoot {
    description
     "The newRoot trap indicates that the sending agent
      has become the new root of the Spanning Tree; the
      trap is sent by a bridge soon after its election
      as the new root, e.g., upon expiration of the
      Topology Change Timer immediately subsequent to
      its election.  Implementation of this trap is
      optional.";
  }

  notification topologyChange {
    description
     "A topologyChange trap is sent by a bridge when
      any of its configured ports transitions from the
      Learning state to the Forwarding state, or from
      the Forwarding state to the Blocking state.  The
      trap is not sent if a newRoot trap is sent for the
      same transition.  Implementation of this trap is
      optional.";
  }

}
