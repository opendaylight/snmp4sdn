module acl {

    yang-version 1;

    namespace
      "urn:opendaylight:snmp4sdn:md:acl";

    prefix acl;

    organization "Netconf Central";

    contact
      "Yi-Ling Hsieh <ylhsieh@itri.org.tw>";

    description
      "YANG version of the SNMP4SDN ACL Service MIB.";

    revision "2015-01-19" {//TODO: update date
      description
        "SNMP4SDN ACL Service module in progress.";
    }

    grouping acl-index{
      leaf profile-id{
        type int32;
      }
      leaf rule-id{
        type int32;
      }
      leaf profile-name{
        type string;
      }
      leaf rule-name{
        type string;
      }
    }

    grouping acl-field{
      leaf src-ip{
        type string;
      }
      leaf dst-ip{
        type string;
      }
      leaf ctrl-vid{
        type int32;
      }
    }

    typedef acl-action{
      type enumeration {
        enum "ACL_ACTIONS_PERMIT" {
         value 1;
        }
        enum "ACL_ACTIONS_DENY" {
         value 0;
        }
      }
    }

    grouping acl-rule{
      leaf-list port-list{
        type int16;
      }
      uses acl-field;
      leaf acl-action{
        type acl-action;
      }
    }

    typedef acl-layer{
      type enumeration {
        enum "ACL_LAYER_ETHERNET" {
         value 1;
        }
        enum "ACL_LAYER_IP" {
         value 2;
        }
      }
    }

    grouping acl-profile{
      leaf acl-layer{
        type acl-layer;
      }
      leaf vlan-mask{
        type int32;//TODO: what's the best type for 0xfff
      }
      leaf src-ip-mask{
        type string;
      }
      leaf dst-ip-mask{
        type string;
      }
    }

    typedef result{
      type enumeration{
        enum "SUCCESS" {
          value 1;
        }
        enum "FAIL" {
          value 2;
        }
        enum "EMPTY" {
          value 3;
        }
        enum "INVALID_PARAM" {
          value 4;
        }
        enum "ALREADY_EXIST" {
          value 5;
        }
        enum "NOT_EXIST" {
          value 6;
        }
        enum "NOT_READY" {
          value 7;
        }
        enum "INTERRUPT" {
          value 8;
        }
      }
    }

    rpc add-acl-rule {
      description
        "Add ACL rule";
      input {
        leaf nodeId {
          type int64;
        }
        uses acl-index;
        uses acl-rule;
      }
      output {
        leaf add-acl-rule-result{
          type result;
      	 }
      }
    }

    rpc del-acl-rule {
      description
        "Delete ACL rule";
      input {
        leaf nodeId {
          type int64;
        }
        uses acl-index;
      }
      output {
        leaf del-acl-rule-result{
          type result;
      	 }
      }
    }

    rpc create-acl-profile {
      description
        "(2)	Create an ACL profile on the switch";
      input {
        leaf nodeId {
          type int64;
        }
        leaf profile-id {
          type int32;
        }
        leaf profile-name {
          type string;
        }
        uses acl-profile;
      }
      output {
        leaf create-acl-profile-result{
          type result;
      	 }
      }
    }

    rpc del-acl-profile {
      description
        "Delete ACL profile on the switch";
      input {
        leaf nodeId {
          type int64;
        }
        leaf profile-id {
          type int32;
        }
        leaf profile-name {
          type string;
        }
      }
      output {
        leaf del-acl-profile-result{
          type result;
      	 }
      }
    }

    rpc get-acl-index-on-switch {
      description
        "Get the rule IDs in each of ACL profiles on the switch";
      input {
        leaf nodeId {
          type int64;
        }
      }
      output {
      	 list acl-index{
          uses acl-index;
        }
      }
    }

  }  // module acl
